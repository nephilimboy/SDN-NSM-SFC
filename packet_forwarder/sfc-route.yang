module sfc-route {
    yang-version 1.1;
    namespace "http://carleton.ca/yang/sfc-route";
    prefix sfc-route;

    organization "Carleton University";
    contact "SFC YANG";
    description "This yang module is for simple routing in sfc environment";
    container sfc_routes {
        config true;
        list route {
            key "protocol";
            leaf protocol {
                type string;
            }
            leaf in_iface {
                type string;
            }
            leaf out_iface {
                type string;
            }
        }
    }
}
